module test-a {
  yang-version 1.1;
  namespace "urn:test-a";
  prefix testa;

  import ietf-netconf-acm {
    prefix nacm;
  }
  import ietf-netconf {
    prefix nc;
  }

  organization
    "Test Organization";
  contact
    "Test Contact";
  description
    "Module Test A";

  revision 2024-03-09 {
    description
      "Revision Description";
    reference
      "Revision Reference";
  }

  feature test-feature {
    description
      "Test Feature";
  }

  identity test-base-identity {
    description
      "Test Identity Base";
  }

  identity test-derived-identity {
    base test-base-identity;
    description
      "Test Derived Identity";
  }

  grouping test-grouping {
    description
      "Test Grouping";
    leaf test-grouping-leaf {
      type uint8;
      description
        "Test Grouping Leaf";
    }
    leaf-list test-grouping-leaf-list {
      type uint8;
      description
        "Test Grouping Leaf List";
    }
  }

  rpc test-apple-de-Finibus-Bonorum-et-Malorum-de-Finibus-Bonorum-et-Malorum {
    description
      "Test Apple";
    input {
      leaf leaf-name {
        type string;
        description
          "Apple input leaf name";
      }
      uses test-grouping;
    }
  }

  notification test-aleph {
    if-feature "test-feature";
    description
      "Test Notification Aleph";
    uses test-grouping;
  }

  notification test-aleph {
    description
      "Test Aleph";
    uses test-grouping;
  }

  deviation "/nacm:nacm" {
    description
      "Lorem ipsum dolor sit amet, consectetur adipiscing elit, sed do eiusmod tempor incididunt ut labore et dolore magna aliqua.";
    deviate add {
      config false;
    }
  }

  deviation "/testa:test-alpha/testa:test-leaf" {
    deviate add {
      default "default-string";
      mandatory true;
    }
    deviate replace {
      config false;
    }
  }

  container test-alpha {
    presence "Test Alpha Presence";
    description
      "Test Alpha";
    uses test-grouping;
    leaf test-leaf {
      type string;
      description
        "Test Leaf Description";
      default "default-string";
      mandatory true;
    }
    choice test-choice {
      description
        "Test Choice";
      case test-case-a {
        description
          "Test Case A";
        leaf test-case-a-leaf {
          type leafref {
            path "/testa:test-alpha/testa:test-leaf";
          }
          description
            "Test Case A Leaf";
        }
      }
      case test-case-b {
        status deprecated;
        description
          "Test Case B";
        leaf test-case-b-leaf {
          type string {
            pattern '[ ]+';
          }
          description
            "Test Case B Leaf";
        }
      }
      case test-case-c {
        description
          "Test Case B";
        leaf test-case-c-leaf {
          type leafref {
            path "/testa:test-alpha/testa:test-grouping-leaf";
          }
          description
            "Test Case C Leaf";
        }
        leaf-list test-case-c-leaf {
          if-feature "test-feature";
          type string;
          default "Something Else";
          description
            "Test Case C Leaf List";
        }
      }
    }
  }
}
